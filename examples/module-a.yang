module module-a {
  namespace "http://example.org/example-module";
  prefix "ma";

  import module-b {
    prefix mb;
  }

  include submodule-a;

  organization "Example Organization";
  contact "example@example.com";
  description "A minimal example module";

  grouping grouping-module-a {
    leaf grouping-leaf-module-a {
      type string;
    }
  }

  container container-module-a {
    leaf leaf-module-a {
      type string;
    }

    uses mb:grouping-module-b;

    uses grouping-submodule-a;
    uses mc:grouping-non-existing;

    uses mb:grouping-submodule-b;
  }
}
