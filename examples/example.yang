module system {
    prefix "sys";
    namespace "org.system";
    yang-version 1.1;

    organization "System Organization";
    contact "test@system.org";
    description "System module";
    reference "See system.com";

    grouping address {
        description "A simple address grouping";

        leaf city {
            type string;
        }
    }

    container testing {
        uses address;


        container system-config {
            description "System configuration container";
            uses address;
        }
    }
}
