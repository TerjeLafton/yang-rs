module example-module {
  namespace "http://example.org/example-module";
  prefix "ma";

  organization "Example Organization";
  contact "example@example.com";
  description "A minimal example module";

  container container-module-a {
    description "A container for example-module";
    leaf leaf-module-a {
      description "A leaf for example-module";
      type string;
    }
  }
}
